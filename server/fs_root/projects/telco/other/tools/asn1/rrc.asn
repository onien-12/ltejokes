RRC DEFINITIONS ::= BEGIN

RadioResourceConfigCommonSIB ::= SEQUENCE {
   rach-ConfigCommon RACH-ConfigCommon,
   bcch-Config BCCH-Config,
   pcch-Config PCCH-Config,
   prach-Config PRACH-ConfigSIB,
   pdsch-ConfigCommon PDSCH-ConfigCommon,
   pusch-ConfigCommon PUSCH-ConfigCommon,
   pucch-ConfigCommon PUCCH-ConfigCommon,
   soundingRS-UL-ConfigCommon SoundingRS-UL-ConfigCommon,
   uplinkPowerControlCommon UplinkPowerControlCommon,
   ul-CyclicPrefixLength UL-CyclicPrefixLength,
   ...,
   [[ uplinkPowerControlCommon-v1020 UplinkPowerControlCommon-v1020 OPTIONAL -- Need OR
   ]],
   [[ rach-ConfigCommon-v1250 RACH-ConfigCommon-v1250 OPTIONAL -- Need OR
   ]],
   [[ pusch-ConfigCommon-v1270 PUSCH-ConfigCommon-v1270 OPTIONAL -- Need OR
   ]],
   [[ bcch-Config-v1310 BCCH-Config-v1310 OPTIONAL, -- Need OR
   pcch-Config-v1310 PCCH-Config-v1310 OPTIONAL, -- Need OR
   freqHoppingParameters-r13 FreqHoppingParameters-r13 OPTIONAL, -- Need OR
   pdsch-ConfigCommon-v1310 PDSCH-ConfigCommon-v1310 OPTIONAL, -- Need OR
   pusch-ConfigCommon-v1310 PUSCH-ConfigCommon-v1310 OPTIONAL, -- Need OR
   prach-ConfigCommon-v1310 PRACH-ConfigSIB-v1310 OPTIONAL, -- Need OR
   pucch-ConfigCommon-v1310 PUCCH-ConfigCommon-v1310 OPTIONAL -- Need OR
   ]],
   [[ highSpeedConfig-r14 HighSpeedConfig-r14 OPTIONAL, -- Need OR
   prach-Config-v1430 PRACH-Config-v1430 OPTIONAL, -- Need OR
   pucch-ConfigCommon-v1430 PUCCH-ConfigCommon-v1430 OPTIONAL -- Need OR
   ]],
   [[ prach-Config-v1530 PRACH-ConfigSIB-v1530 OPTIONAL, -- Cond EDT
   ce-RSS-Config-r15 RSS-Config-r15 OPTIONAL, -- Need OR
   wus-Config-r15 WUS-Config-r15 OPTIONAL, -- Need OR
   highSpeedConfig-v1530 HighSpeedConfig-v1530 OPTIONAL -- Need OR
   ]],
   [[ uplinkPowerControlCommon-v1540 UplinkPowerControlCommon-v1530 OPTIONAL -- Need OR
   ]],
   [[ wus-Config-v1560 WUS-Config-v1560 OPTIONAL -- Need OR
   ]],
   [[
   wus-Config-v1610 WUS-Config-v1610 OPTIONAL, -- Need OR
   highSpeedConfig-v1610 HighSpeedConfig-v1610 OPTIONAL, -- Need OR
   crs-ChEstMPDCCH-ConfigCommon-r16 CRS-ChEstMPDCCH-ConfigCommon-r16 OPTIONAL, -- Need OR
   gwus-Config-r16 GWUS-Config-r16 OPTIONAL, -- Need OR
   uplinkPowerControlCommon-v1610 UplinkPowerControlCommon-v1610 OPTIONAL, -- Need OR
   rss-MeasConfig-r16 ENUMERATED { enabled } OPTIONAL, -- Need OR
   rss-MeasNonNCL-r16 ENUMERATED { enabled } OPTIONAL, -- Need OR
   puncturedSubcarriersDL-r16 BIT STRING (SIZE (2)) OPTIONAL, -- Need OR
   highSpeedInterRAT-NR-r16 BOOLEAN OPTIONAL -- Need OR
   ]]
}

HighSpeedConfig-r14 ::= SEQUENCE {
   highSpeedEnhancedMeasFlag-r14 ENUMERATED { true } OPTIONAL, -- Need OR
   highSpeedEnhancedDemodulationFlag-r14 ENUMERATED { true } OPTIONAL -- Need OR
}

PRACH-Config-v1430 ::= SEQUENCE {
   rootSequenceIndexHighSpeed-r14 INTEGER (0..837),
   zeroCorrelationZoneConfigHighSpeed-r14 INTEGER (0..12),
   prach-ConfigIndexHighSpeed-r14 INTEGER (0..63),
   prach-FreqOffsetHighSpeed-r14 INTEGER (0..94)
}

PUCCH-ConfigCommon-v1430 ::= SEQUENCE {
   pucch-NumRepetitionCE-Msg4-Level3-r14 ENUMERATED { n64, n128 } OPTIONAL -- Need OR
}

PRACH-ConfigSIB-v1530 ::= SEQUENCE {
   edt-PRACH-ParametersListCE-r15 SEQUENCE (SIZE (1..maxCE-Level-r13)) OF EDT-PRACH-ParametersCE-r15
}

EDT-PRACH-ParametersCE-r15 ::= SEQUENCE {
   edt-PRACH-ParametersCE-r15 SEQUENCE {
      prach-ConfigIndex-r15 INTEGER (0..63),
      prach-FreqOffset-r15 INTEGER (0..94),
      prach-StartingSubframe-r15 ENUMERATED { sf2, sf4, sf8, sf16, sf32, sf64, sf128, sf256 } OPTIONAL, -- Need OP
      mpdcch-NarrowbandsToMonitor-r15 SEQUENCE (SIZE (1..2)) OF INTEGER (1..maxAvailNarrowBands-r13)
      } OPTIONAL -- Need OR
}

RSS-Config-r15 ::= SEQUENCE {
   duration-r15 ENUMERATED { sf8, sf16, sf32, sf40 } ,
   freqLocation-r15 INTEGER (0..98),
   periodicity-r15 ENUMERATED { ms160, ms320, ms640, ms1280 } ,
   powerBoost-r15 ENUMERATED { dB0, dB3, dB4dot8, dB6 } ,
   timeOffset-r15 INTEGER (0..31)
}

WUS-Config-r15 ::= SEQUENCE {
   maxDurationFactor-r15 ENUMERATED { one32th, one16th, one8th, one4th } ,
   numPOs-r15 ENUMERATED { n1, n2, n4, spare1 } DEFAULT n1,
   freqLocation-r15 ENUMERATED { n0, n2, n4, spare1 } ,
   timeOffsetDRX-r15 ENUMERATED { ms40, ms80, ms160, ms240 } ,
   timeOffset-eDRX-Short-r15 ENUMERATED { ms40, ms80, ms160, ms240 } ,
   timeOffset-eDRX-Long-r15 ENUMERATED { ms1000, ms2000 } OPTIONAL -- Need OP
}

HighSpeedConfig-v1530 ::= SEQUENCE {
   highSpeedMeasGapCE-ModeA-r15 ENUMERATED { true }
}

UplinkPowerControlCommon-v1530 ::= SEQUENCE {
   deltaFList-SPUCCH-r15 DeltaFList-SPUCCH-r15
}

WUS-Config-v1560 ::= SEQUENCE {
   powerBoost-r15 ENUMERATED { dB0, dB1dot8, dB3, dB4dot8 }
}

WUS-Config-v1610 ::= SEQUENCE {
   numDRX-CyclesRelaxed-r16 ENUMERATED { n1, n2, n4, n8 }
}

HighSpeedConfig-v1610 ::= SEQUENCE {
   highSpeedEnhMeasFlag2-r16 ENUMERATED { true } OPTIONAL, -- Need OR
   highSpeedEnhDemodFlag2-r16 ENUMERATED { true } OPTIONAL -- Need OR
}

CRS-ChEstMPDCCH-ConfigCommon-r16 ::= SEQUENCE {
   powerRatio-r16 ENUMERATED { dB-4dot77, dB-3, dB-1dot77, dB0, dB1, dB2, dB3, dB4dot77 }
}

GWUS-Config-r16 ::= SEQUENCE {
   groupAlternation-r16 ENUMERATED { true } OPTIONAL, -- Need OR
   commonSequence-r16 ENUMERATED { g0, g126 } OPTIONAL, -- Need OR
   timeParameters-r16 GWUS-TimeParameters-r16 OPTIONAL, -- Cond NoWUSr15
   resourceConfigDRX-r16 GWUS-ResourceConfig-r16,
   resourceConfig-eDRX-Short-r16 GWUS-ResourceConfig-r16 OPTIONAL, -- Need OP
   resourceConfig-eDRX-Long-r16 GWUS-ResourceConfig-r16 OPTIONAL, -- Cond TimeOffset
   probThreshList-r16 GWUS-ProbThreshList-r16 OPTIONAL, -- Cond ProbabilityBased
   groupNarrowBandList-r16 GWUS-GroupNarrowBandList-r16 OPTIONAL -- Need OR
}

GWUS-TimeParameters-r16 ::= SEQUENCE {
   maxDurationFactor-r16 ENUMERATED { one32th, one16th, one8th, one4th } ,
   numPOs-r16 ENUMERATED { n1, n2, n4, spare1 } DEFAULT n1,
   timeOffsetDRX-r16 ENUMERATED { ms40, ms80, ms160, ms240 } ,
   timeOffset-eDRX-Short-r16 ENUMERATED { ms40, ms80, ms160, ms240 } ,
   timeOffset-eDRX-Long-r16 ENUMERATED { ms1000, ms2000 } OPTIONAL, -- Need OP
   numDRX-CyclesRelaxed-r16 ENUMERATED { n1, n2, n4, n8 } OPTIONAL, -- Need OR
   powerBoost-r16 ENUMERATED { dB0, dB1dot8, dB3, dB4dot8 } OPTIONAL, -- Need OR
   ...
}

GWUS-ResourceConfig-r16 ::= SEQUENCE {
   resourceMappingPattern-r16 CHOICE {
      resourceLocationWithWUS ENUMERATED { primary, secondary, primary3FDM } ,
      resourceLocationWithoutWUS ENUMERATED { n0, n2 }
      },
   numGroupsList-r16 GWUS-NumGroupsList-r16 OPTIONAL, -- Need OP
   groupsForServiceList-r16 GWUS-GroupsForServiceList-r16 OPTIONAL -- Cond ProbabilityBased
}

UplinkPowerControlCommon-v1610 ::= SEQUENCE {
   alphaSRS-Add-r16 Alpha-r12,
   p0-NominalSRS-Add-r16 INTEGER (-126..24)
}

GWUS-GroupsForServiceList-r16 ::= SEQUENCE (SIZE (1..maxGWUS-ProbThresholds-r16)) OF INTEGER (1..maxGWUS-Groups-1-r16)

GWUS-GroupNarrowBandList-r16 ::= SEQUENCE (SIZE (1..maxAvailNarrowBands-r13)) OF BOOLEAN

GWUS-NumGroupsList-r16 ::= SEQUENCE (SIZE (1..maxGWUS-Resources-r16)) OF GWUS-NumGroups-r16

GWUS-ProbThreshList-r16 ::= SEQUENCE (SIZE (1..maxGWUS-ProbThresholds-r16)) OF GWUS-PagingProbThresh-r16

GWUS-NumGroups-r16 ::= ENUMERATED { n1, n2, n4, n8 }

GWUS-PagingProbThresh-r16 ::= ENUMERATED { p20, p30, p40, p50, p60, p70, p80, p90 }

PRACH-ParametersListCE-r13 ::= SEQUENCE (SIZE (1..maxCE-Level-r13)) OF PRACH-ParametersCE-r13

PRACH-ParametersCE-r13 ::= SEQUENCE {
   prach-ConfigIndex-r13 INTEGER (0..63),
   prach-FreqOffset-r13 INTEGER (0..94),
   prach-StartingSubframe-r13 ENUMERATED { sf2, sf4, sf8, sf16, sf32, sf64, sf128,
      sf256 } OPTIONAL, -- Need OP
   maxNumPreambleAttemptCE-r13
   ENUMERATED { n3, n4, n5, n6, n7, n8, n10 } OPTIONAL, -- Need OP
   numRepetitionPerPreambleAttempt-r13 ENUMERATED { n1,n2,n4,n8,n16,n32,n64,n128 } ,
   mpdcch-NarrowbandsToMonitor-r13 SEQUENCE (SIZE (1..2)) OF
   INTEGER (1..maxAvailNarrowBands-r13),
   mpdcch-NumRepetition-RA-r13 ENUMERATED { r1, r2, r4, r8, r16,
      r32, r64, r128, r256 } ,
   prach-HoppingConfig-r13 ENUMERATED { on,off }
}

PUSCH-ConfigCommon ::= SEQUENCE {
   pusch-ConfigBasic SEQUENCE {
      n-SB INTEGER (1..4),
      hoppingMode ENUMERATED { interSubFrame, intraAndInterSubFrame } ,
      pusch-HoppingOffset INTEGER (0..98),
      enable64QAM BOOLEAN
      },
   ul-ReferenceSignalsPUSCH UL-ReferenceSignalsPUSCH
}

UL-ReferenceSignalsPUSCH ::= SEQUENCE {
   groupHoppingEnabled BOOLEAN,
   groupAssignmentPUSCH INTEGER (0..29),
   sequenceHoppingEnabled BOOLEAN,
   cyclicShift INTEGER (0..7)
}

PUCCH-ConfigCommon ::= SEQUENCE {
   deltaPUCCH-Shift ENUMERATED { ds1, ds2, ds3 } ,
   nRB-CQI INTEGER (0..98),
   nCS-AN INTEGER (0..7),
   n1PUCCH-AN INTEGER (0..2047)
}

SoundingRS-UL-ConfigCommon ::= CHOICE {
   release NULL,
   setup SEQUENCE {
      srs-BandwidthConfig ENUMERATED { bw0, bw1, bw2, bw3, bw4, bw5, bw6, bw7 } ,
      srs-SubframeConfig ENUMERATED {
         sc0, sc1, sc2, sc3, sc4, sc5, sc6, sc7,
         sc8, sc9, sc10, sc11, sc12, sc13, sc14, sc15 } ,
      ackNackSRS-SimultaneousTransmission BOOLEAN,
      srs-MaxUpPts ENUMERATED { true } OPTIONAL -- Cond TDD
      }
}

UplinkPowerControlCommon ::= SEQUENCE {
   p0-NominalPUSCH INTEGER (-126..24),
   alpha Alpha-r12,
   p0-NominalPUCCH INTEGER (-127..-96),
   deltaFList-PUCCH DeltaFList-PUCCH,
   deltaPreambleMsg3 INTEGER (-1..6)
}

DeltaFList-PUCCH ::= SEQUENCE {
   deltaF-PUCCH-Format1 ENUMERATED { deltaF-2, deltaF0, deltaF2 } ,
   deltaF-PUCCH-Format1b ENUMERATED { deltaF1, deltaF3, deltaF5 } ,
   deltaF-PUCCH-Format2 ENUMERATED { deltaF-2, deltaF0, deltaF1, deltaF2 } ,
   deltaF-PUCCH-Format2a ENUMERATED { deltaF-2, deltaF0, deltaF2 } ,
   deltaF-PUCCH-Format2b ENUMERATED { deltaF-2, deltaF0, deltaF2 }
}

UL-CyclicPrefixLength ::= ENUMERATED { len1, len2 }

PCCH-Config ::= SEQUENCE {
   defaultPagingCycle ENUMERATED {
      rf32, rf64, rf128, rf256 } ,
   nB ENUMERATED {
      fourT, twoT, oneT, halfT, quarterT, oneEighthT,
      oneSixteenthT, oneThirtySecondT }
}

BCCH-Config ::= SEQUENCE {
   modificationPeriodCoeff ENUMERATED { n2, n4, n8, n16 }
}

UplinkPowerControlCommon-v1020 ::= SEQUENCE {
   deltaF-PUCCH-Format3-r10 ENUMERATED { deltaF-1, deltaF0, deltaF1, deltaF2,
      deltaF3, deltaF4, deltaF5, deltaF6 } ,
   deltaF-PUCCH-Format1bCS-r10 ENUMERATED { deltaF1, deltaF2, spare2, spare1 }
}

UplinkPowerControlCommon-v1310 ::= SEQUENCE {
   deltaF-PUCCH-Format4-r13 ENUMERATED { deltaF16, deltaF15, deltaF14,deltaF13, deltaF12,
      deltaF11, deltaF10, spare1 } OPTIONAL, -- Need OR
   deltaF-PUCCH-Format5-13 ENUMERATED { deltaF13, deltaF12, deltaF11, deltaF10, deltaF9,
      deltaF8, deltaF7, spare1 } OPTIONAL -- Need OR
}

UplinkPowerControlCommon-v1530 ::= SEQUENCE {
   deltaFList-SPUCCH-r15 DeltaFList-SPUCCH-r15
}

RACH-ConfigCommon-v1250 ::= SEQUENCE {
   txFailParams-r12 SEQUENCE {
      connEstFailCount-r12 ENUMERATED { n1, n2, n3, n4 } ,
      connEstFailOffsetValidity-r12 ENUMERATED { s30, s60, s120, s240,
         s300, s420, s600, s900 } ,
      connEstFailOffset-r12 INTEGER (0..15) OPTIONAL -- Need OP
      }
}

RACH-ConfigCommon ::= SEQUENCE {
   preambleInfo SEQUENCE {
      numberOfRA-Preambles ENUMERATED {
         n4, n8, n12, n16, n20, n24, n28,
         n32, n36, n40, n44, n48, n52, n56,
         n60, n64 } ,
      preamblesGroupAConfig SEQUENCE {
         sizeOfRA-PreamblesGroupA ENUMERATED {
            n4, n8, n12, n16, n20, n24, n28,
            n32, n36, n40, n44, n48, n52, n56,
            n60 } ,
         messageSizeGroupA ENUMERATED { b56, b144, b208, b256 } ,
         messagePowerOffsetGroupB ENUMERATED {
            minusinfinity, dB0, dB5, dB8, dB10, dB12,
            dB15, dB18 } ,
         ...
         } OPTIONAL -- Need OP
      },
   powerRampingParameters PowerRampingParameters,
   ra-SupervisionInfo SEQUENCE {
      preambleTransMax PreambleTransMax,
      ra-ResponseWindowSize ENUMERATED {
         sf2, sf3, sf4, sf5, sf6, sf7,
         sf8, sf10 } ,
      mac-ContentionResolutionTimer ENUMERATED {
         sf8, sf16, sf24, sf32, sf40, sf48,
         sf56, sf64 }
      },
   maxHARQ-Msg3Tx INTEGER (1..8),
   ...,
   [[ preambleTransMax-CE-r13 PreambleTransMax OPTIONAL, -- Need OR
   rach-CE-LevelInfoList-r13 RACH-CE-LevelInfoList-r13 OPTIONAL -- Need OR
   ]],
   [[ edt-SmallTBS-Subset-r15 ENUMERATED { true } OPTIONAL -- Cond EDT-OR
   ]]
}

RACH-CE-LevelInfoList-r13 ::= SEQUENCE (SIZE (1..maxCE-Level-r13)) OF RACH-CE-LevelInfo-r13

RACH-CE-LevelInfo-r13 ::= SEQUENCE {
   preambleMappingInfo-r13 SEQUENCE {
      firstPreamble-r13 INTEGER(0..63),
      lastPreamble-r13 INTEGER(0..63)
      },
   ra-ResponseWindowSize-r13 ENUMERATED { sf20, sf50, sf80, sf120, sf180,
      sf240, sf320, sf400 } ,
   
   mac-ContentionResolutionTimer-r13 ENUMERATED { sf80, sf100, sf120,
      sf160, sf200, sf240, sf480, sf960 } ,
   rar-HoppingConfig-r13 ENUMERATED { on,off } ,
   ...,
   [[ edt-Parameters-r15 SEQUENCE {
      edt-LastPreamble-r15 INTEGER(0..63),
      edt-SmallTBS-Enabled-r15 BOOLEAN,
      edt-TBS-r15 ENUMERATED { b328, b408, b504, b600, b712,
         b808, b936, b1000or456 } ,
      mac-ContentionResolutionTimer-r15 ENUMERATED { sf240, sf480, sf960,
         sf1920, sf3840, sf5760, sf7680, sf10240 } OPTIONAL -- Need OP
      } OPTIONAL -- Cond EDT
   ]]
}

PowerRampingParameters ::= SEQUENCE {
   powerRampingStep ENUMERATED { dB0, dB2,dB4, dB6 } ,
   preambleInitialReceivedTargetPower ENUMERATED {
      dBm-120, dBm-118, dBm-116, dBm-114, dBm-112,
      dBm-110, dBm-108, dBm-106, dBm-104, dBm-102,
      dBm-100, dBm-98, dBm-96, dBm-94,
      dBm-92, dBm-90 }
}

PUSCH-ConfigCommon-v1270 ::= SEQUENCE {
   enable64QAM-v1270 ENUMERATED { true }
}

PreambleTransMax ::= ENUMERATED {
   n3, n4, n5, n6, n7, n8, n10, n20, n50,
n100, n200 }

BCCH-Config-v1310 ::= SEQUENCE {
   modificationPeriodCoeff-v1310 ENUMERATED { n64 }
}

Alpha-r12 ::= ENUMERATED { al0, al04, al05, al06, al07, al08, al09, al1 }

FreqHoppingParameters-r13 ::= SEQUENCE {
   dummy ENUMERATED { nb2, nb4 } OPTIONAL,
   dummy2 CHOICE {
      interval-FDD-r13 ENUMERATED { int1, int2, int4, int8 } ,
      interval-TDD-r13 ENUMERATED { int1, int5, int10, int20 }
      } OPTIONAL,
   dummy3 CHOICE {
      interval-FDD-r13 ENUMERATED { int2, int4, int8, int16 } ,
      interval-TDD-r13 ENUMERATED { int5, int10, int20, int40 }
      } OPTIONAL,
   interval-ULHoppingConfigCommonModeA-r13 CHOICE {
      interval-FDD-r13 ENUMERATED { int1, int2, int4, int8 } ,
      interval-TDD-r13 ENUMERATED { int1, int5, int10, int20 }
      } OPTIONAL, -- Cond MP-A
   interval-ULHoppingConfigCommonModeB-r13 CHOICE {
      interval-FDD-r13 ENUMERATED { int2, int4, int8, int16 } ,
      interval-TDD-r13 ENUMERATED { int5, int10, int20, int40 }
      } OPTIONAL, -- Cond MP-B
   dummy4 INTEGER (1..maxAvailNarrowBands-r13) OPTIONAL
}

PUCCH-ConfigCommon-v1310 ::= SEQUENCE {
   n1PUCCH-AN-InfoList-r13 N1PUCCH-AN-InfoList-r13 OPTIONAL, -- Need OR
   pucch-NumRepetitionCE-Msg4-Level0-r13 ENUMERATED { n1, n2, n4, n8 } OPTIONAL, -- Need OR
   pucch-NumRepetitionCE-Msg4-Level1-r13 ENUMERATED { n1, n2, n4, n8 } OPTIONAL, -- Need OR
   pucch-NumRepetitionCE-Msg4-Level2-r13 ENUMERATED { n4, n8, n16, n32 } OPTIONAL, -- Need OR
   pucch-NumRepetitionCE-Msg4-Level3-r13 ENUMERATED { n4, n8, n16, n32 } OPTIONAL -- Need OR
}

N1PUCCH-AN-InfoList-r13 ::= SEQUENCE (SIZE (1..maxCE-Level-r13)) OF INTEGER (0..2047)

PUSCH-ConfigCommon-v1310 ::= SEQUENCE {
   pusch-maxNumRepetitionCEmodeA-r13 ENUMERATED {
      r8, r16, r32 } OPTIONAL, -- Need OR
   pusch-maxNumRepetitionCEmodeB-r13 ENUMERATED {
      r192, r256, r384, r512, r768, r1024,
      r1536, r2048 } OPTIONAL, -- Need OR
   pusch-HoppingOffset-v1310
   INTEGER (1..maxAvailNarrowBands-r13) OPTIONAL -- Need OR
}

RSRP-ThresholdsPrachInfoList-r13 ::= SEQUENCE (SIZE (1..3)) OF RSRP-Range

PCCH-Config-v1310 ::= SEQUENCE {
   paging-narrowBands-r13 INTEGER (1..maxAvailNarrowBands-r13),
   mpdcch-NumRepetition-Paging-r13 ENUMERATED { r1, r2, r4, r8, r16, r32, r64, r128, r256 } ,
   nB-v1310 ENUMERATED { one64thT, one128thT, one256thT }
   OPTIONAL -- Need OR
}

PHICH-Config ::= SEQUENCE {
   phich-Duration ENUMERATED { normal, extended } ,
   phich-Resource ENUMERATED { oneSixth, half, one, two }
}

PDSCH-ConfigCommon ::= SEQUENCE {
   referenceSignalPower INTEGER (-60..50),
   p-b INTEGER (0..3)
}

PDSCH-ConfigCommon-v1310 ::= SEQUENCE {
   pdsch-maxNumRepetitionCEmodeA-r13 ENUMERATED {
      r16, r32 } OPTIONAL, -- Need OR
   pdsch-maxNumRepetitionCEmodeB-r13 ENUMERATED {
      r192, r256, r384, r512, r768, r1024,
      r1536, r2048 } OPTIONAL -- Need OR
}

PRACH-ConfigSIB ::= SEQUENCE {
   rootSequenceIndex INTEGER (0..837),
   prach-ConfigInfo PRACH-ConfigInfo
}

PRACH-ConfigSIB-v1310 ::= SEQUENCE {
   rsrp-ThresholdsPrachInfoList-r13 RSRP-ThresholdsPrachInfoList-r13,
   mpdcch-startSF-CSS-RA-r13 CHOICE {
      fdd-r13 ENUMERATED { v1, v1dot5, v2, v2dot5, v4, v5, v8,
         v10 } ,
      tdd-r13 ENUMERATED { v1, v2, v4, v5, v8, v10, v20, spare }
      } OPTIONAL, -- Cond MP
   prach-HoppingOffset-r13 INTEGER (0..94) OPTIONAL, -- Need OR
   prach-ParametersListCE-r13 PRACH-ParametersListCE-r13
}

PRACH-ConfigSIB-v1530 ::= SEQUENCE {
   edt-PRACH-ParametersListCE-r15 SEQUENCE (SIZE (1..maxCE-Level-r13)) OF EDT-PRACH-ParametersCE-r15
}

PRACH-ConfigInfo ::= SEQUENCE {
   prach-ConfigIndex INTEGER (0..63),
   highSpeedFlag BOOLEAN,
   zeroCorrelationZoneConfig INTEGER (0..15),
   prach-FreqOffset INTEGER (0..94)
}

DeltaFList-SPUCCH-r15 ::= CHOICE {
   release NULL,
   setup SEQUENCE {
      deltaF-slotSPUCCH-Format1-r15 ENUMERATED { deltaF-1, deltaF0, deltaF1, deltaF2,
         deltaF3, deltaF4, deltaF5, deltaF6 } OPTIONAL, -- Need OR
      deltaF-slotSPUCCH-Format1a-r15 ENUMERATED { deltaF1, deltaF2, deltaF3, deltaF4,
         deltaF5, deltaF6, deltaF7, deltaF8 } OPTIONAL, -- Need OR
      deltaF-slotSPUCCH-Format1b-r15 ENUMERATED { deltaF3, deltaF4, deltaF5, deltaF6,
         deltaF7, deltaF8, deltaF9, deltaF10 } OPTIONAL, -- Need OR
      deltaF-slotSPUCCH-Format3-r15 ENUMERATED { deltaF4, deltaF5, deltaF6, deltaF7,
         deltaF8, deltaF9, deltaF10, deltaF11 } OPTIONAL, -- Need OR
      deltaF-slotSPUCCH-RM-Format4-r15 ENUMERATED { deltaF13, deltaF14, deltaF15, deltaF16,
         deltaF17, deltaF18, deltaF19, deltaF20 } OPTIONAL,
      --Need OR
      deltaF-slotSPUCCH-TBCC-Format4-r15 ENUMERATED { deltaF10, deltaF11, deltaF12, deltaF13,
         deltaF14, deltaF15, deltaF16, deltaF17 } OPTIONAL,
      --Need OR
      deltaF-subslotSPUCCH-Format1and1a-r15 ENUMERATED { deltaF5, deltaF6, deltaF7, deltaF8,
         deltaF9, deltaF10, deltaF11, deltaF12 } OPTIONAL,
      --Need OR
      deltaF-subslotSPUCCH-Format1b-r15 ENUMERATED { deltaF6, deltaF7, deltaF8, deltaF9,
         deltaF10, deltaF11, deltaF12, deltaF13 } OPTIONAL,
      --Need OR
      deltaF-subslotSPUCCH-RM-Format4-r15 ENUMERATED { deltaF15, deltaF16, deltaF17, deltaF18,
         deltaF19, deltaF20, deltaF21, deltaF22 } OPTIONAL,
      --Need OR
      deltaF-subslotSPUCCH-TBCC-Format4-r15 ENUMERATED { deltaF10, deltaF11, deltaF12, deltaF13,
         deltaF14, deltaF15, deltaF16, deltaF17 } OPTIONAL,
      --Need OR
      ...
      }
}

RSRP-Range ::= INTEGER(0..97)

maxGWUS-ProbThresholds-r16 INTEGER ::= 3
maxGWUS-Groups-1-r16 INTEGER ::= 31 
maxGWUS-Resources-r16 INTEGER ::= 4
maxAvailNarrowBands-r13 INTEGER ::= 16 
maxCE-Level-r13 INTEGER ::= 4 

END
